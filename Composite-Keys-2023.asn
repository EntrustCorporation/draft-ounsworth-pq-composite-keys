-- command for easily copying it into a compiler (ubuntu with xclip)
-- cat ASN1ModuleIncludes.asn Composite-Keys-2023.asn | xclip -sel clip


Composite-Keys-2023
           {iso(1) identified-organization(3) dod(6) internet(1) security(5)
       mechanisms(5) pkix(7) id-mod(0) id-mod-composite-keys(TBD)}

DEFINITIONS IMPLICIT TAGS ::= BEGIN

EXPORTS ALL;

IMPORTS
  PUBLIC-KEY, SIGNATURE-ALGORITHM, ParamOptions, AlgorithmIdentifier{}
    FROM AlgorithmInformation-2009  -- RFC 5912 [X509ASN1]
      { iso(1) identified-organization(3) dod(6) internet(1)
        security(5) mechanisms(5) pkix(7) id-mod(0)
        id-mod-algorithmInformation-02(58) }

  SubjectPublicKeyInfo
    FROM PKIX1Explicit-2009
      { iso(1) identified-organization(3) dod(6) internet(1)
        security(5) mechanisms(5) pkix(7) id-mod(0)
        id-mod-pkix1-explicit-02(51) }

  OneAsymmetricKey
    FROM AsymmetricKeyPackageModuleV1
      { iso(1) member-body(2) us(840) rsadsi(113549) pkcs(1)
        pkcs-9(9) smime(16) modules(0)
        id-mod-asymmetricKeyPkgV1(50) }


  NamedCurve
    FROM PKIXAlgs-2009 { iso(1) identified-organization(3) dod(6)
     internet(1) security(5) mechanisms(5) pkix(7) id-mod(0)
     id-mod-pkix1-algorithms2008-02(56) }


  pk-Ed25519, pk-X25519, pk-X448
    FROM Safecurves-pkix-18
    { iso(1) identified-organization(3) dod(6) internet(1)
      security(5) mechanisms(5) pkix(7) id-mod(0)
      id-mod-safecurves-pkix(93) } ;


--
-- Object Identifiers
--
 
der OBJECT IDENTIFIER ::=
  {joint-iso-itu-t asn1(1) ber-derived(2) distinguished-encoding(1)}


--  COMPOSITE-KEY-ALGORITHM
--
--  Describes the basic properties of a composite key algorithm
--
--  &id - contains the OID identifying the composite algorithm
--  &Params - if present, contains the type for the algorithm
--               parameters; if absent, implies no parameters
--  &paramPresence - parameter presence requirement
--
-- }

COMPOSITE-KEY-ALGORITHM ::= CLASS {
    &id             OBJECT IDENTIFIER UNIQUE,
    &Params         OPTIONAL,
    &paramPresence  ParamOptions DEFAULT absent
} WITH SYNTAX {
    IDENTIFIER &id
    [PARAMS [TYPE &Params] ARE &paramPresence ]
}

--
-- Public Key
--

CompositePublicKey ::= SEQUENCE SIZE (2..MAX) OF SubjectPublicKeyInfo

CompositePublicKeyOs ::= OCTET STRING (CONTAINING CompositePublicKey ENCODED BY der)

CompositePublicKeyBs ::= BIT STRING (CONTAINING CompositePublicKey ENCODED BY der)

CompositePrivateKey ::= SEQUENCE SIZE (2..MAX) OF OneAsymmetricKey

--
-- Composite public key information objects
--


-- The following ASN.1 object class then automatically generates the
-- public key structure from the types defined in pk-explicitComposite.

-- ExplicitCompositePublicKey - The data structure for a composite
-- public key sec-composite-pub-keys and SecondPublicKeyType are needed
-- because PUBLIC-KEY contains a set of public key types, not a single
-- type.
-- TODO The parameters should be optional only if they are marked
-- optional in the PUBLIC-KEY


ExplicitCompositePublicKey{PUBLIC-KEY:firstPublicKey, FirstPublicKeyType,
  PUBLIC-KEY:secondPublicKey, SecondPublicKeyType} ::= SEQUENCE {
    firstPublicKey SEQUENCE {
        params firstPublicKey.&Params OPTIONAL,
        publicKey FirstPublicKeyType
    },
    secondPublicKey SEQUENCE {
        params secondPublicKey.&Params OPTIONAL,
        publicKey SecondPublicKeyType
    }
}

pk-explicitCompositeSignature{OBJECT IDENTIFIER:id, PUBLIC-KEY:firstPublicKey,
  FirstPublicKeyType, PUBLIC-KEY:secondPublicKey, SecondPublicKeyType}
  PUBLIC-KEY ::= {
    IDENTIFIER id
    KEY ExplicitCompositePublicKey{firstPublicKey, FirstPublicKeyType,
      secondPublicKey, SecondPublicKeyType}
    PARAMS ARE absent
    CERT-KEY-USAGE { digitalSignature, nonRepudiation, keyCertSign, cRLSign }
}

pk-explicitCompositeKEM{OBJECT IDENTIFIER:id, PUBLIC-KEY:firstPublicKey,
  FirstPublicKeyType, PUBLIC-KEY:secondPublicKey, SecondPublicKeyType}
  PUBLIC-KEY ::= {
    IDENTIFIER id
    KEY ExplicitCompositePublicKey{firstPublicKey, FirstPublicKeyType,
      secondPublicKey, SecondPublicKeyType}
    PARAMS ARE absent
    CERT-KEY-USAGE { keyEncipherment }
}


-- TODO this is one possible way to reference specific named curves.
-- But I don't think this compiles.

--pk-ECDSA-P256 PUBLIC-KEY ::= {
--  IDENTIFIER id-ecPublicKey
--  KEY ECPoint
--  PARAMS TYPE NamedCurve.secp256r1 ARE required }
--
--pk-ECDSA-brainpoolP256r1 PUBLIC-KEY ::= {
--  IDENTIFIER id-ecPublicKey
--  KEY ECPoint
--  PARAMS NamedCurve{brainpoolP256r1} }
--
--pk-ECDSA-P384 PUBLIC-KEY ::= {
--  IDENTIFIER id-ecPublicKey
--  KEY ECPoint
--  PARAMS TYPE NamedCurve{secp384r1} }
--
--pk-ECDSA-brainpoolP384r1 PUBLIC-KEY ::= {
--  IDENTIFIER id-ecPublicKey
--  KEY ECPoint
--  PARAMS NamedCurve{brainpoolP384r1} }



-- Explicit Composite Signature Keys

-- TODO: To be replaced by IANA
id-Dilithium3-RSA-PSS OBJECT IDENTIFIER ::= {
  joint-iso-itu-t(2) country(16) us(840) organization(1) entrust(114027)
  algorithm(80) explicitcomposite(5) signature(1) dilithium3-rsa-pss(14) }

pk-Dilithium3-RSA-PSS PUBLIC-KEY ::= 
  pk-explicitCompositeSignature{id-Dilithium3-RSA-PSS, pk-Dilithium3TBD,
  OCTET STRING, pk-rsaSSA-PSS, OCTET STRING}


-- TODO: To be replaced by IANA
id-Dilithium3-RSA-PKCS15-SHA256 OBJECT IDENTIFIER ::= {
  joint-iso-itu-t(2) country(16) us(840) organization(1) entrust(114027)
  algorithm(80) explicitcomposite(5) signature(1) dilithium3-rsa(1) }

pk-Dilithium3-RSA-PKCS15-SHA256 PUBLIC-KEY ::= 
  pk-explicitCompositeSignature{id-Dilithium3-RSA-PKCS15-SHA256, 
  pk-Dilithium3TBD, OCTET STRING, pk-rsa, RSAPublicKey}


-- TODO: To be replaced by IANA
id-Dilithium3-ECDSA-P256-SHA256 OBJECT IDENTIFIER ::= {
  joint-iso-itu-t(2) country(16) us(840) organization(1) entrust(114027)
  algorithm(80) explicitcomposite(5) signature(1) dilithium3-rsa(2) }

pk-Dilithium3-ECDSA-P256-SHA256 PUBLIC-KEY ::= 
  pk-explicitCompositeSignature{id-Dilithium3-ECDSA-P256-SHA256, 
  pk-Dilithium3TBD, OCTET STRING, pk-ECDSA-P256, ECPoint}

--TODO: this is missing `PARAMS secp256r1`

  
-- TODO: To be replaced by IANA
id-Dilithium3-ECDSA-brainpoolP256r1 OBJECT IDENTIFIER ::= {
  joint-iso-itu-t(2) country(16) us(840) organization(1) entrust(114027)
  algorithm(80) explicitcomposite(5) signature(1)  
  dilithium3-ecdsa-brainpoolp256r1(3) }

pk-Dilithium3-ECDSA-brainpoolP256r1 PUBLIC-KEY ::= 
  pk-explicitCompositeSignature{id-Dilithium3-ECDSA-brainpoolP256r1, 
  pk-Dilithium3TBD, OCTET STRING, pk-ec, ECPoint}

--TODO: this is missing `PARAMS brainpoolP256r1`


-- TODO: To be replaced by IANA
id-Dilithium3-Ed25519 OBJECT IDENTIFIER ::= {
  joint-iso-itu-t(2) country(16) us(840) organization(1) entrust(114027)
  algorithm(80) explicitcomposite(5) signature(1) dilithium3-ed25519(4) }

pk-Dilithium3-Ed25519 PUBLIC-KEY ::= 
  pk-explicitCompositeSignature{id-Dilithium3-Ed25519, 
  pk-Dilithium3TBD, OCTET STRING, pk-Ed25519, OCTET STRING}


-- TODO: To be replaced by IANA
id-Dilithium5-ECDSA-P384 OBJECT IDENTIFIER ::= {
  joint-iso-itu-t(2) country(16) us(840) organization(1) entrust(114027)
  algorithm(80) explicitcomposite(5) signature(1) dilithium5-ecdsa-p384(5) }

pk-Dilithium5-ECDSA-P384 PUBLIC-KEY ::= 
  pk-explicitCompositeSignature{id-Dilithium5-ECDSA-P384, 
  pk-Dilithium5TBD, OCTET STRING, pk-ec, ECPoint}

--TODO: this is missing `PARAMS secp384r1`


-- TODO: To be replaced by IANA
id-Dilithium5-ECDSA-brainpoolP384r1 OBJECT IDENTIFIER ::= {
  joint-iso-itu-t(2) country(16) us(840) organization(1) entrust(114027)
  algorithm(80) explicitcomposite(5) signature(1) dilithium5-ecdsa-brainpoolp384r1(6) }

pk-Dilithium5-ECDSA-brainpoolP384r1 PUBLIC-KEY ::= 
  pk-explicitCompositeSignature{id-Dilithium5-ECDSA-brainpoolP384r1, 
  pk-Dilithium5TBD, OCTET STRING, pk-ec, ECPoint}

--TODO: this is missing `PARAMS brainpoolP384r1`



-- TODO: To be replaced by IANA
id-Dilithium5-Ed448 OBJECT IDENTIFIER ::= {
  joint-iso-itu-t(2) country(16) us(840) organization(1) entrust(114027)
  algorithm(80) explicitcomposite(5) signature dilithium5-ed448(7) }

pk-Dilithium5-Ed448 PUBLIC-KEY ::= 
  pk-explicitCompositeSignature{id-Dilithium5-Ed448, 
  pk-Dilithium5TBD, OCTET STRING, pk-Ed25519, OCTET STRING}

--TODO: I have a question out to LAMPS about why there is no pk-Ed448. See: https://mailarchive.ietf.org/arch/msg/spasm/bJHcxCA3bXoqKHqXnZ85Vrixu68/


-- TODO: To be replaced by IANA
id-Falcon512-ECDSA-P256-SHA256 OBJECT IDENTIFIER ::= {
  joint-iso-itu-t(2) country(16) us(840) organization(1) entrust(114027)
  algorithm(80) explicitcomposite(5) signature falcon512-ecdsa-p256-sha256(8) }

pk-Falcon512-ECDSA-P256-SHA256 PUBLIC-KEY ::= 
  pk-explicitCompositeSignature{id-Falcon512-ECDSA-P256-SHA256, 
  pk-falcon512TBD, OCTET STRING, pk-ec, ECPoint}

--TODO: this is missing `PARAMS secp256r1`


-- TODO: To be replaced by IANA
id-Falcon512-ECDSA-brainpoolP256r1-SHA256 OBJECT IDENTIFIER ::= {
  joint-iso-itu-t(2) country(16) us(840) organization(1) entrust(114027)
  algorithm(80) explicitcomposite(5) signature(1) falcon512-ecdsa-brainpoolp256r1-sha256(9) }

pk-Falcon512-ECDSA-brainpoolP256r1-SHA256 PUBLIC-KEY ::= 
  pk-explicitCompositeSignature{id-Falcon512-ECDSA-brainpoolP256r1-SHA256, 
  pk-falcon512TBD, OCTET STRING, pk-ec, ECPoint}

--TODO: this is missing `PARAMS brainpoolp256r1`



-- TODO: To be replaced by IANA
id-Falcon512-Ed25519 OBJECT IDENTIFIER ::= {
  joint-iso-itu-t(2) country(16) us(840) organization(1) entrust(114027)
  algorithm(80) explicitcomposite(5) signatur(1) falcon512-ed25519(10) }

pk-Falcon512-Ed25519 PUBLIC-KEY ::= 
  pk-explicitCompositeSignature{id-Falcon512-Ed25519, 
  pk-falcon512TBD, OCTET STRING, pk-Ed25519, OCTET STRING}


-- Explicit Composite KEM Keys


-- TODO: To be replaced by IANA
id-Kyber512-ECDH-P256-KMAC128 OBJECT IDENTIFIER ::= {
  joint-iso-itu-t(2) country(16) us(840) organization(1) entrust(114027)
  algorithm(80) explicitcomposite(5) explicitcomposite-kem(2) id-kyber512-ecdh-p256(1) }

pk-Kyber512-ECDH-P256-KMAC128 PUBLIC-KEY ::= 
  pk-explicitCompositeKEM{id-Kyber512-ECDH-P256-KMAC128, 
  pk-Kyber512TBD, OCTET STRING, pk-ec, ECPoint}

--TODO: this is missing `PARAMS secp256r1`


-- TODO: To be replaced by IANA
id-Kyber512-ECDH-brainpoolP256r1-KMAC128 OBJECT IDENTIFIER ::= {
  joint-iso-itu-t(2) country(16) us(840) organization(1) entrust(114027)
  algorithm(80) explicitcomposite(5) explicitcomposite-kem(2) id-kyber512-ecdh-brainpoolp256r1(2) }

pk-Kyber512-ECDH-brainpoolP256r1-KMAC128 PUBLIC-KEY ::= 
  pk-explicitCompositeKEM{id-Kyber512-ECDH-brainpoolP256r1-KMAC128, 
  pk-Kyber512TBD, OCTET STRING, pk-ec, ECPoint}

--TODO: this is missing `PARAMS brainpoolp256r1`


-- TODO: To be replaced by IANA
id-Kyber512-X25519-KMAC128 OBJECT IDENTIFIER ::= {
  joint-iso-itu-t(2) country(16) us(840) organization(1) entrust(114027)
  algorithm(80) explicitcomposite(5) kem(2)
  id-kyber512-x25519(3) }

pk-Kyber512-X25519-KMAC128 PUBLIC-KEY ::= 
  pk-explicitCompositeKEM{id-Kyber512-X25519-KMAC128, 
  pk-Kyber512TBD, OCTET STRING, pk-X25519, OCTET STRING}


-- TODO: To be replaced by IANA
id-Kyber768-RSA-KMAC256 OBJECT IDENTIFIER ::= {
  joint-iso-itu-t(2) country(16) us(840) organization(1) entrust(114027)
  algorithm(80) explicitcomposite(5) kem(2)
  id-kyber768-rsa(4) }

pk-Kyber768-RSA-KMAC256 PUBLIC-KEY ::= 
  pk-explicitCompositeKEM{id-Kyber768-RSA-KMAC256, 
  pk-Kyber768TBD, OCTET STRING, pk-rsa, RSAPublicKey}


-- TODO: To be replaced by IANA
id-Kyber768-ECDH-P256-KMAC256 OBJECT IDENTIFIER ::= {
  joint-iso-itu-t(2) country(16) us(840) organization(1) entrust(114027)
  algorithm(80) explicitcomposite(5) kem(2)
  id-kyber768-ecdh-p256(5) }

pk-Kyber768-ECDH-P256-KMAC256 PUBLIC-KEY ::= 
  pk-explicitCompositeKEM{id-Kyber768-ECDH-P256-KMAC256, 
  pk-Kyber768TBD, OCTET STRING, pk-ec, ECPoint}

--TODO: this is missing `PARAMS secp256r1`


id-Kyber768-ECDH-brainpoolP256r1-KMAC256 OBJECT IDENTIFIER ::= {
  joint-iso-itu-t(2) country(16) us(840) organization(1) entrust(114027)
  algorithm(80) explicitcomposite(5) kem(2)
  id-kyber768-ecdh-p256(6) }

pk-Kyber768-ECDH-brainpoolP256r1-KMAC256 PUBLIC-KEY ::= 
  pk-explicitCompositeKEM{id-Kyber768-ECDH-brainpoolP256r1-KMAC256, 
  pk-Kyber768TBD, OCTET STRING, pk-ec, ECPoint}

--TODO: this is missing `PARAMS brainpoolp256r1`


-- TODO: To be replaced by IANA
id-Kyber768-X25519-KMAC256 OBJECT IDENTIFIER ::= {
  joint-iso-itu-t(2) country(16) us(840) organization(1) entrust(114027)
  algorithm(80) explicitcomposite(5) kem(2)
  id-kyber768-x25519(7) }

pk-Kyber768-X25519-KMAC256 PUBLIC-KEY ::= 
  pk-explicitCompositeKEM{id-Kyber768-X25519-KMAC256, 
  pk-Kyber768TBD, OCTET STRING, pk-X25519, OCTET STRING}



-- TODO: To be replaced by IANA
id-Kyber1024-ECDH-P384-KMAC256 OBJECT IDENTIFIER ::= {
  joint-iso-itu-t(2) country(16) us(840) organization(1) entrust(114027)
  algorithm(80) explicitcomposite(5) kem(2)
  id-kyber1024-ecdh-p384(8) }

pk-Kyber1024-ECDH-P384-KMAC256 PUBLIC-KEY ::= 
  pk-explicitCompositeKEM{id-Kyber1024-ECDH-P384-KMAC256, 
  pk-Kyber1024TBD, OCTET STRING, pk-ec, ECPoint}

--TODO: this is missing `PARAMS secp384r1`


-- TODO: To be replaced by IANA
id-Kyber1024-ECDH-brainpoolP384r1-KMAC256 OBJECT IDENTIFIER ::= {
  joint-iso-itu-t(2) country(16) us(840) organization(1) entrust(114027)
  algorithm(80) explicitcomposite(5) kem(2)
  id-kyber1024-ecdh-brainpoolp384r1(9) }

pk-Kyber1024-ECDH-brainpoolP384r1-KMAC256 PUBLIC-KEY ::= 
  pk-explicitCompositeKEM{id-Kyber1024-ECDH-brainpoolP384r1-KMAC256, 
  pk-Kyber1024TBD, OCTET STRING, pk-ec, ECPoint}

--TODO: this is missing `PARAMS brainpoolp384r1`


-- TODO: To be replaced by IANA
id-Kyber1024-X448-KMAC256 OBJECT IDENTIFIER ::= {
  joint-iso-itu-t(2) country(16) us(840) organization(1) entrust(114027)
  algorithm(80) explicitcomposite(5) kem(2)
  id-kyber1024-x448(10) }

pk-Kyber1024-X448-KMAC256 PUBLIC-KEY ::= 
  pk-explicitCompositeKEM{id-Kyber1024-X448-KMAC256, 
  pk-Kyber1024TBD, OCTET STRING, pk-X448, OCTET STRING}


END
